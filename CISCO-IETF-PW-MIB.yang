/*
 * This YANG module has been generated by smidump 0.5.0:
 *
 *      smidump -f yang CISCO-IETF-PW-MIB
 *
 * Do not edit. Edit the source file instead!
 */

module CISCO-IETF-PW-MIB {

  namespace "urn:ietf:params:xml:ns:yang:smiv2:CISCO-IETF-PW-MIB";
  prefix "cisco-ietf-pw";

  import CISCO-IETF-PW-TC-MIB {
    prefix "cisco-ietf";
  }

  import CISCO-SMI {
    prefix "cisco-smi";
  }

  import INET-ADDRESS-MIB {
    prefix "inet-address";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   " 
    Thomas D. Nadeau 
    Postal: Cisco Systems, Inc. 
            250 Apollo Drive 
            Chelmsford, MA 01824 
    Tel:    +1-978-497-3051 
    Email:  tnadeau@cisco.com 
    
    MPLS MIB Development Team
    Postal: Cisco Systems, Inc.
            250 Apollo Drive
            Chelmsford, MA 01924
    Tel:    +1-978-497-3989
    Email:  ch-mpls-mib-dev@cisco.com";

  description
   "This MIB contains managed object definitions for Pseudo 
    Wire operation as in: Pate, P., et al, <draft-ietf-pwe3- 
    framework>, Xiao, X., et al, <draft-ietf-pwe3- 
    requirements>, Martini, L., et al, <draft-martini- 
    l2circuit-trans-mpls>, and Martini, L., et al, 
    <draft-martini-l2circuit-encap-mpls>. 
    
    The indexes for this MIB are also used to index the PSN- 
    specific tables and the VC-specific tables. The VC Type 
    dictates which VC-specific MIB to use. For example, a  
    'cep' VC Type requires the use the configuration and status  
    tables within the CEP-MIB. 
    
    This MIB enable the use of any underlying packet switched  
    network (PSN). Specific tables for the MPLS PSN is 
    currently defined in a separate CISCO-IETF-PW-MPLS-MIB. 
    Tables to support other PSNs (IP, L2TP for example) will 
    be added to this MIB in future revisions. 
    
    At the time of publication of this version, there are no  
    PWE3 WG documents for all features and objects in this MIB, 
    and the MIB is therefore subject to change based on the WG  
    progress.";

  revision 2004-03-17 {
    description
     "1) Added notifications group:
      -cpwVcUpDownNotifEnable
      -cpwVcNotifRate
      -cpwVcDown
      -cpwVcUp
      2) Added CANA OID value ciscoExperiment.106
      3) updated based on MIB police comments
      -replaced un-cisco-ized variable names w/
      cisco-ized names in descriptions (e.g. pwVcxxx
      replaced w/ cpwVcxxx)";
  }

  revision 2003-02-26 {
    description
     "Made Cisco proprietary based on the PW-MIB.my file
      extracted from draft-ietf-pwe3-pw-mib-00.txt";
  }

  revision 2002-05-26 {
    description
     "Moved to draft-ietf-00 status. Changes from previous draft: 
      1) Change name of pwVcPriority to pwVcSetUpPriority and  
         added pwVcHoldingPriority. 
      2) Add pwVcIdMappingTable and pwVcPeersMappingTable to help  
         ordered query of the MIB tables for EMS applications. 
      3) Clarification to work in progress objects. 
      4) Editorial and typos in descriptions. 
      5) Added pwVcPerfTotalDiscontinuityTime and  
         pwVcPerfIntervalTimeElapsed.  
      6) Remove 32 bit counters. ";
  }

  revision 2002-01-30 {
    description
     " Changes from -01 draft: 
      1) Inbound and outbound clarification and name changes. 
      2) Removing pwVcPeerIpv4Addr and pwVcPeerIpv6Addr,   
         replacing them with pwVcPeerAddr and adding type for  
         address type selection. 
      3) Adding type for VC OperStatus. 
      4) Adding pwVcTimeElapsed and pwVcValidIntervals. ";
  }

  revision 2001-11-07 {
    description
     "Changes from -00 draft: 
      1) Remove VcInstance from tables indexes in order to simplify 
         the MIB. 
      2) Removing APS 1+1 table. 
      3) Changing hdlcCisco to hdlc in pwVcType. 
      4) Add description of VC label at pending PW signaling stage. 
      5) Add interval valid object in interval performance tables. 
      6) Remove VC APS notification. 
      7) Change 'conservative'/'liberal' to 'strict'/'loose'. 
      8) Add objects for interface MTU, use of control word, 
         interface string. 
      9) Ordering of objects based on functionality. 
      10) Update operation of pwVcOperStatus.  ";
  }

  revision 2001-07-11 {
    description
     "draft-00 version";
  }


  container CISCO-IETF-PW-MIB {
    config false;

    container cpwVcObjects {
      smiv2:oid "1.3.6.1.4.1.9.10.106.1";

      leaf cpwVcIndexNext {
        type uint32;
        description
         "This object contains an appropriate value to be used 
          for cpwVcIndex when creating entries in the 
          cpwVcTable. The value 0 indicates that no 
          unassigned entries are available.  To obtain the 
          value of cpwVcIndex for a new entry in the 
          cpwVcTable, the manager issues a management 
          protocol retrieval operation to obtain the current 
          value of cpwVcIndex.  After each retrieval 
          operation, the agent should modify the value to 
          reflect the next unassigned index.  After a manager 
          retrieves a value the agent will determine through 
          its local policy when this index value will be made 
          available for reuse.";
        smiv2:max-access "read-only";
        smiv2:oid "1.3.6.1.4.1.9.10.106.1.1";
      }

      leaf cpwVcPerfTotalErrorPackets {
        type yang:counter64;
        description
         "Counter for number of error at VC level processing, for  
          example packets received with unknown VC label.";
        smiv2:max-access "read-only";
        smiv2:oid "1.3.6.1.4.1.9.10.106.1.6";
      }

      leaf cpwVcUpDownNotifEnable {
        type boolean;
        description
         "If this object is set to true(1), then it enables
          the emission of cpwVcUp and cpwVcDown
          notifications; otherwise these notifications are not
          emitted.";
        reference
         "See also RFC3413 for explanation that 
          notifications are under the ultimate control of the 
          MIB modules in this document.";
        smiv2:defval "false";
        smiv2:max-access "read-write";
        smiv2:oid "1.3.6.1.4.1.9.10.106.1.9";
      }

      leaf cpwVcNotifRate {
        type uint32;
        description
         "This object defines the maximum number of PW VC notifications
          that can be emitted from the device per second.";
        smiv2:max-access "read-write";
        smiv2:oid "1.3.6.1.4.1.9.10.106.1.10";
      }
    }

    container cpwVcTable {
      description
       "This table specifies information for connecting various 
        emulated services to various tunnel type.";
      smiv2:oid "1.3.6.1.4.1.9.10.106.1.2";

      list cpwVcEntry {
        key "cpwVcIndex";
        description
         "A row in this table represents an emulated virtual 
          connection (VC) across a packet network. It is indexed by 
          cpwVcIndex, which uniquely identifying a singular  
          connection. ";
        smiv2:oid "1.3.6.1.4.1.9.10.106.1.2.1";

        leaf cpwVcIndex {
          type cisco-ietf:CpwVcIndexType;
          description
           "Index for the conceptual row identifying a VC within  
            this PW Emulation VC table.";
          smiv2:max-access "not-accessible";
          smiv2:oid "1.3.6.1.4.1.9.10.106.1.2.1.1";
        }

        leaf cpwVcType {
          type cisco-ietf:CpwVcType;
          description
           "This value indicate the service to be carried over 
            this VC.  
            Note: the exact set of VC types is yet to be worked  
            out by the WG. ";
          smiv2:max-access "read-write";
          smiv2:oid "1.3.6.1.4.1.9.10.106.1.2.1.2";
        }

        leaf cpwVcOwner {
          type enumeration {
            enum "manual" {
              value "1";
            }
            enum "maintenanceProtocol" {
              value "2";
            }
            enum "other" {
              value "3";
            }
          }
          description
           "Set by the operator to indicate the protocol responsible  
            for establishing this VC. Value 'manual' is used in all 
            cases where no maintenance protocol (PW signaling) is used  
            to set-up the VC, i.e. require configuration of entries in 
            the VC tables including VC labels, etc. The value  
            'maintenanceProtocol' is used in case of standard 
            signaling of the VC for the specific PSN, for example LDP 
            for MPLS PSN as specified in <draft- draft-martini- 
            l2circuit-trans-mpls> or L2TP control protocol.  
            Value 'other' is used for other types of signaling.";
          smiv2:max-access "read-write";
          smiv2:oid "1.3.6.1.4.1.9.10.106.1.2.1.3";
        }

        leaf cpwVcPsnType {
          type enumeration {
            enum "mpls" {
              value "1";
            }
            enum "l2tp" {
              value "2";
            }
            enum "ip" {
              value "3";
            }
            enum "mplsOverIp" {
              value "4";
            }
            enum "gre" {
              value "5";
            }
            enum "other" {
              value "6";
            }
          }
          description
           "Set by the operator to indicate the PSN type on which this  
            VC will be carried. Based on this object, the relevant PSN  
            table entries are created in the in the PSN specific MIB  
            modules. For example, if mpls(1) is defined, the agent  
            create an entry in cpwVcMplsTable, which further define the  
            MPLS PSN configuration. 
            Note: the exact set of PSN types is yet to be worked  
            out by the WG. ";
          smiv2:max-access "read-write";
          smiv2:oid "1.3.6.1.4.1.9.10.106.1.2.1.4";
        }

        leaf cpwVcSetUpPriority {
          type int32 {
            range "0..7";
          }
          description
           "This object define the relative set-up priority of the VC   
            in a lowest-to-highest fashion, where 0 is the highest  
            priority. VCs with the same priority are treated with 
            equal priority. Dropped VC will be set 'dormant' (as 
            indicated in cpwVcOperStatus). 
            This value is significant if there are competing resources 
            between VCs and the implementation support this feature. 
            If not supported or not relevant, the value of zero MUST 
            be used.";
          smiv2:defval "0";
          smiv2:max-access "read-write";
          smiv2:oid "1.3.6.1.4.1.9.10.106.1.2.1.5";
        }

        leaf cpwVcHoldingPriority {
          type int32 {
            range "0..7";
          }
          description
           "This object define the relative holding priority of the VC   
            in a lowest-to-highest fashion, where 0 is the highest  
            priority. VCs with the same priority are treated with 
            equal priority. Dropped VC will be set 'dormant' (as 
            indicated in cpwVcOperStatus). 
            This value is significant if there are competing resources 
            between VCs and the implementation support this feature. 
            If not supported or not relevant, the value of zero MUST 
            be used.";
          smiv2:defval "0";
          smiv2:max-access "read-write";
          smiv2:oid "1.3.6.1.4.1.9.10.106.1.2.1.6";
        }

        leaf cpwVcInboundMode {
          type enumeration {
            enum "loose" {
              value "1";
            }
            enum "strict" {
              value "2";
            }
          }
          description
           "This object is used to enable greater security for  
            implementation that use per platform VC label space. In  
            strict mode, packets coming from the PSN are accepted only  
            from tunnels that are associated to the same VC via the  
            inbound tunnel table in the case of MPLS, or as identified  
            by the source IP address in case of L2TP or IP PSN. The  
            entries in the inbound tunnel table are either explicitly  
            configured or implicitly known by the maintenance protocol  
            used for VC set-up. 
            
            If such association is not known, not configured or not  
            desired, loose mode should be configured, and the node  
            should accept the packet based on the VC label only  
            regardless of the outer tunnel used to carry the VC.";
          smiv2:defval "loose";
          smiv2:max-access "read-write";
          smiv2:oid "1.3.6.1.4.1.9.10.106.1.2.1.7";
        }

        leaf cpwVcPeerAddrType {
          type inet-address:InetAddressType;
          description
           "Denotes the address type of the peer node maintenance 
            protocol (signaling) address if PW maintenance protocol is 
            used for the VC creation. It should be set to  
            'unknown' if PE/PW maintenance protocol is not used,  
            i.e. cpwVcOwner is set to 'manual'. ";
          smiv2:defval "ipv4";
          smiv2:max-access "read-write";
          smiv2:oid "1.3.6.1.4.1.9.10.106.1.2.1.8";
        }

        leaf cpwVcPeerAddr {
          type inet-address:InetAddress;
          description
           "This object contains the value of of the peer node address 
            of the PW/PE maintenance protocol entity. This object  
            should contain a value of 0 if not relevant (manual  
            configuration of the VC).";
          smiv2:max-access "read-write";
          smiv2:oid "1.3.6.1.4.1.9.10.106.1.2.1.9";
        }

        leaf cpwVcID {
          type cisco-ietf:CpwVcIDType;
          description
           "Used in the outgoing VC ID field within the 'Virtual 
            Circuit FEC Element' when LDP signaling is used or PW ID  
            AVP for L2TP.";
          reference
           "Martini, et al, <draft-martini-l2circuit-trans-mpls>. 
            and So, et al, <draft-so-pwe3-ethernet>.  
            Note: as specified in l2circuit-trans: It is REQUIRED to 
            assign the same VC ID, and VC type for a given circuit in 
            both directions.";
          smiv2:max-access "read-write";
          smiv2:oid "1.3.6.1.4.1.9.10.106.1.2.1.10";
        }

        leaf cpwVcLocalGroupID {
          type cisco-ietf:CpwGroupID;
          description
           "Used in the Group ID field sent to the peer PWES  
            within the maintenance protocol used for VC setup,  
            zero if not used.";
          reference
           "Martini, et al, <draft-martini-l2circuit-trans-mpls> 
            and So, et al, <draft-so-pwe3-ethernet.txt>.";
          smiv2:max-access "read-write";
          smiv2:oid "1.3.6.1.4.1.9.10.106.1.2.1.11";
        }

        leaf cpwVcControlWord {
          type boolean;
          description
           "Define if the control word will be sent with each packet by  
            the local node.";
          reference
           "Martini, et al, <draft-martini-l2circuit-trans-mpls>";
          smiv2:defval "false";
          smiv2:max-access "read-write";
          smiv2:oid "1.3.6.1.4.1.9.10.106.1.2.1.12";
        }

        leaf cpwVcLocalIfMtu {
          type uint32 {
            range "0..65535";
          }
          description
           "If not equal zero, the optional IfMtu object in the  
            maintenance protocol will be sent with this value,  
            representing the locally supported MTU size over the  
            interface (or the virtual interface) associated with the  
            VC.";
          reference
           "Martini, et al, <draft-martini-l2circuit-trans-mpls> 
            and So, et al, <draft-so-pwe3-ethernet>.";
          smiv2:defval "0";
          smiv2:max-access "read-write";
          smiv2:oid "1.3.6.1.4.1.9.10.106.1.2.1.13";
        }

        leaf cpwVcLocalIfString {
          type boolean;
          description
           "Each VC is associated to an interface (or a virtual  
            interface) in the ifTable of the node as part of the 
            service configuration. This object defines if the  
            maintenance protocol will send the interface's name as 
            appears on the ifTable in the name object as part of the 
            maintenance protocol. If set to false, the optional element 
            will not be sent.";
          reference
           "Martini, et al, <draft-martini-l2circuit-trans-mpls> 
            and So, et al, <draft-so-pwe3-ethernet.txt>.";
          smiv2:defval "false";
          smiv2:max-access "read-write";
          smiv2:oid "1.3.6.1.4.1.9.10.106.1.2.1.14";
        }

        leaf cpwVcRemoteGroupID {
          type cisco-ietf:CpwGroupID;
          description
           "Obtained from the Group ID field as received via the  
            maintenance protocol used for VC setup, zero if not used.  
            Value of 0xFFFF shall be used if the object is yet to be  
            defined by the VC maintenance protocol.";
          reference
           "Martini, et al, <draft-martini-l2circuit-trans-mpls> 
            and So, et al, <draft-so-pwe3-ethernet.txt>.";
          smiv2:max-access "read-only";
          smiv2:oid "1.3.6.1.4.1.9.10.106.1.2.1.15";
        }

        leaf cpwVcRemoteControlWord {
          type enumeration {
            enum "noControlWord" {
              value "1";
            }
            enum "withControlWord" {
              value "2";
            }
            enum "notYetKnown" {
              value "3";
            }
          }
          description
           "If maintenance protocol is used for VC establishment, this  
            parameter indicates the received status of the control word  
            usage, i.e. if packets will be received with control word 
            or not. The value of 'notYetKnown' is used while the 
            maintenance protocol has not yet received the indication  
            from the remote node. 
            In manual configuration of the VC this parameters indicate  
            to the local node what is the expected encapsulation for 
            the received packets. ";
          reference
           "Martini, et al, <draft-martini-l2circuit-trans-mpls> 
            and So, et al, <draft-so-pwe3-ethernet.txt>.";
          smiv2:max-access "read-write";
          smiv2:oid "1.3.6.1.4.1.9.10.106.1.2.1.16";
        }

        leaf cpwVcRemoteIfMtu {
          type uint32;
          description
           "The remote interface MTU as (optionally) received from the 
            remote node via the maintenance protocol. Should be zero if 
            this parameter is not available or not used.";
          reference
           "Martini, et al, <draft-martini-l2circuit-trans-mpls> 
            and So, et al, <draft-so-pwe3-ethernet.txt>.";
          smiv2:max-access "read-only";
          smiv2:oid "1.3.6.1.4.1.9.10.106.1.2.1.17";
        }

        leaf cpwVcRemoteIfString {
          type snmp-framework:SnmpAdminString {
            length "0..80";
          }
          description
           "Indicate the interface description string as received by 
            the maintenance protocol, MUST be NULL string if not  
            applicable or not known yet.";
          reference
           "Martini, et al, <draft-martini-l2circuit-trans-mpls> 
            and So, et al, <draft-so-pwe3-ethernet>.";
          smiv2:max-access "read-only";
          smiv2:oid "1.3.6.1.4.1.9.10.106.1.2.1.18";
        }

        leaf cpwVcOutboundVcLabel {
          type uint32;
          description
           "The VC label used in the outbound direction (i.e. toward  
            the PSN). It may be set up manually if owner is 'manual' or  
            automatically otherwise. Examples: For MPLS PSN, it  
            represents the 20 bits of VC tag, for L2TP it represent the 
            32 bits Session ID. 
            If the label is not yet known (signaling in process), the  
            object should return a value of 0xFFFF.";
          reference
           "Martini, et al, <draft-martini-l2circuit-trans-mpls> 
            Townsley, et al, <draft-ietf-l2tpext-l2tp-base.txt>";
          smiv2:max-access "read-write";
          smiv2:oid "1.3.6.1.4.1.9.10.106.1.2.1.19";
        }

        leaf cpwVcInboundVcLabel {
          type uint32;
          description
           "The VC label used in the inbound direction (i.e. packets  
            received from the PSN. It may be set up manually if owner 
            is 'manual' or automatically otherwise.  
            Examples: For MPLS PSN, it represents the 20 bits of VC 
            tag, for L2TP it represent the 32 bits Session ID. 
            If the label is not yet known (signaling in process), the  
            object should return a value of 0xFFFF.";
          reference
           "Martini, et al, <draft-martini-l2circuit-trans-mpls> 
            Townsley, et al, <draft-ietf-l2tpext-l2tp-base.txt>";
          smiv2:max-access "read-write";
          smiv2:oid "1.3.6.1.4.1.9.10.106.1.2.1.20";
        }

        leaf cpwVcName {
          type snmp-framework:SnmpAdminString;
          description
           "The canonical name assigned to the VC.";
          smiv2:max-access "read-write";
          smiv2:oid "1.3.6.1.4.1.9.10.106.1.2.1.21";
        }

        leaf cpwVcDescr {
          type snmp-framework:SnmpAdminString;
          description
           "A textual string containing information about the VC.  
            If there is no description this object contains a zero 
            length string.";
          smiv2:max-access "read-write";
          smiv2:oid "1.3.6.1.4.1.9.10.106.1.2.1.22";
        }

        leaf cpwVcCreateTime {
          type yang:timestamp;
          description
           "System time when this VC was created.";
          smiv2:max-access "read-only";
          smiv2:oid "1.3.6.1.4.1.9.10.106.1.2.1.23";
        }

        leaf cpwVcUpTime {
          type yang:timeticks;
          description
           "Number of consecutive ticks this VC has been 'up' in 
            both directions together (i.e. 'up' is observed in  
            cpwVcOperStatus.)";
          smiv2:max-access "read-only";
          smiv2:oid "1.3.6.1.4.1.9.10.106.1.2.1.24";
        }

        leaf cpwVcAdminStatus {
          type enumeration {
            enum "up" {
              value "1";
            }
            enum "down" {
              value "2";
            }
            enum "testing" {
              value "3";
            }
          }
          description
           "The desired operational status of this VC.";
          smiv2:max-access "read-write";
          smiv2:oid "1.3.6.1.4.1.9.10.106.1.2.1.25";
        }

        leaf cpwVcOperStatus {
          type cisco-ietf:CpwOperStatus;
          description
           "Indicates the actual combined operational status of this  
            VC. It is 'up' if both cpwVcInboundOperStatus and  
            cpwVcOutboundOperStatus are in 'up' state. For all other  
            values, if the VCs in both directions are of the same 
            value it reflects that value, otherwise it is set to the 
            most severe status out of the two statuses. The order of  
            severance from most severe to less severe is: unknown,  
            notPresent, down, lowerLayerDown, dormant, testing, up. 
            The operator may consult the per direction OperStatus for 
            fault isolation per direction.";
          smiv2:max-access "read-only";
          smiv2:oid "1.3.6.1.4.1.9.10.106.1.2.1.26";
        }

        leaf cpwVcInboundOperStatus {
          type cisco-ietf:CpwOperStatus;
          description
           "Indicates the actual operational status of this VC in the  
            inbound direction. 
            
            - down:           if PW signaling has not yet finished, or 
                              indications available at the service  
                              level indicate that the VC is not  
                              passing packets. 
            - testing:        if AdminStatus at the VC level is set to  
                              test. 
            - dormant:        The VC is not available because of the 
                              required resources are occupied VC with  
                              higher priority VCs . 
            - notPresent:     Some component is missing to accomplish  
                              the set up of the VC. 
            - lowerLayerDown: The underlying PSN is not in OperStatus  
                              'up'.  ";
          smiv2:max-access "read-only";
          smiv2:oid "1.3.6.1.4.1.9.10.106.1.2.1.27";
        }

        leaf cpwVcOutboundOperStatus {
          type cisco-ietf:CpwOperStatus;
          description
           "Indicates the actual operational status of this VC in the  
            outbound direction 
            - down:           if PW signaling has not yet finished, or 
                              indications available at the service  
                              level indicate that the VC is not 
                              passing packets. 
            - testing:        if AdminStatus at the VC level is set to  
                              test. 
            - dormant:        The VC is not available because of the 
                              required resources are occupied VC with  
                              higher priority VCs . 
            - notPresent:     Some component is missing to accomplish  
                              the set up of the VC. 
            - lowerLayerDown: The underlying PSN is not in OperStatus  
                              'up'.  ";
          smiv2:max-access "read-only";
          smiv2:oid "1.3.6.1.4.1.9.10.106.1.2.1.28";
        }

        leaf cpwVcTimeElapsed {
          type int32 {
            range "1..900";
          }
          description
           "The number of seconds, including partial seconds, 
            that have elapsed since the beginning of the current 
            measurement period. If, for some reason, such as an 
            adjustment in the system's time-of-day clock, the 
            current interval exceeds the maximum value, the 
            agent will return the maximum value.";
          smiv2:max-access "read-only";
          smiv2:oid "1.3.6.1.4.1.9.10.106.1.2.1.29";
        }

        leaf cpwVcValidIntervals {
          type int32 {
            range "0..96";
          }
          description
           "The number of previous 15-minute intervals 
            for which data was collected.  
            An agent with PW capability must be capable of supporting at  
            least n intervals. The minimum value of n is 4, The default  
            of n is 32 and the maximum value of n is 96. 
            The value will be <n> unless the measurement was (re-)  
            started within the last (<n>*15) minutes, in which case the  
            value will be the number of complete 15 minute intervals for  
            which the agent has at least some data. In certain cases  
            (e.g., in the case where the agent is a proxy) it is  
            possible that some intervals are unavailable.  In this case,  
            this interval is the maximum interval number for which data  
            is available. ";
          smiv2:max-access "read-only";
          smiv2:oid "1.3.6.1.4.1.9.10.106.1.2.1.30";
        }

        leaf cpwVcRowStatus {
          type snmpv2-tc:RowStatus;
          description
           "For creating, modifying, and deleting this row.";
          smiv2:max-access "read-write";
          smiv2:oid "1.3.6.1.4.1.9.10.106.1.2.1.31";
        }

        leaf cpwVcStorageType {
          type snmpv2-tc:StorageType;
          description
           "This variable indicates the storage type for this 
            object.";
          smiv2:max-access "read-write";
          smiv2:oid "1.3.6.1.4.1.9.10.106.1.2.1.32";
        }
      }
    }

    container cpwVcPerfCurrentTable {
      description
       "This table provides per-VC performance information for the  
        current interval.";
      smiv2:oid "1.3.6.1.4.1.9.10.106.1.3";

      list cpwVcPerfCurrentEntry {
        key "cpwVcIndex";
        description
         "An entry in this table is created by the agent for 
          every VC.";
        smiv2:oid "1.3.6.1.4.1.9.10.106.1.3.1";

        leaf cpwVcIndex {
          type leafref {
            path "/cisco-ietf-pw:CISCO-IETF-PW-MIB/cisco-ietf-pw:cpwVcTable/cisco-ietf-pw:cpwVcEntry/cisco-ietf-pw:cpwVcIndex";
          }
        }

        leaf cpwVcPerfCurrentInHCPackets {
          type yang:counter64;
          description
           "High capacity counter for number of packets received 
            by the VC (from the PSN) in the current 15 minute 
            interval.";
          smiv2:max-access "read-only";
          smiv2:oid "1.3.6.1.4.1.9.10.106.1.3.1.1";
        }

        leaf cpwVcPerfCurrentInHCBytes {
          type yang:counter64;
          description
           "High capacity counter for number of bytes received 
            by the VC (from the PSN) in the current 15 minute 
            interval.";
          smiv2:max-access "read-only";
          smiv2:oid "1.3.6.1.4.1.9.10.106.1.3.1.2";
        }

        leaf cpwVcPerfCurrentOutHCPackets {
          type yang:counter64;
          description
           "High capacity counter for number of packets forwarded 
            by the VC (to the PSN) in the current 15 minute interval.";
          smiv2:max-access "read-only";
          smiv2:oid "1.3.6.1.4.1.9.10.106.1.3.1.3";
        }

        leaf cpwVcPerfCurrentOutHCBytes {
          type yang:counter64;
          description
           "High capacity counter for number of bytes forwarded 
            by the VC (to the PSN) in the current 15 minute interval.";
          smiv2:max-access "read-only";
          smiv2:oid "1.3.6.1.4.1.9.10.106.1.3.1.4";
        }
      }
    }

    container cpwVcPerfIntervalTable {
      description
       "This table provides per-VC performance information for  
        each interval.";
      smiv2:oid "1.3.6.1.4.1.9.10.106.1.4";

      list cpwVcPerfIntervalEntry {
        key "cpwVcIndex cpwVcPerfIntervalNumber";
        description
         "An entry in this table is created agent for every VC.";
        smiv2:oid "1.3.6.1.4.1.9.10.106.1.4.1";

        leaf cpwVcIndex {
          type leafref {
            path "/cisco-ietf-pw:CISCO-IETF-PW-MIB/cisco-ietf-pw:cpwVcTable/cisco-ietf-pw:cpwVcEntry/cisco-ietf-pw:cpwVcIndex";
          }
        }

        leaf cpwVcPerfIntervalNumber {
          type int32 {
            range "1..96";
          }
          description
           "A number N, between 1 and 96, which identifies the 
            interval for which the set of statistics is available. 
            The interval identified by 1 is the most recently 
            completed 15 minute interval, and the interval identified 
            by N is the interval immediately preceding the one 
            identified by N-1. 
            The minimum range of N is 1 through 4. The default range 
            is 1 to 32. The maximum range of N is 1 through 96. ";
          reference
           "Tesink, K. 'Definitions of Managed Objects for the 
            SONET/SDH Interface Type', RFC 2558";
          smiv2:max-access "not-accessible";
          smiv2:oid "1.3.6.1.4.1.9.10.106.1.4.1.1";
        }

        leaf cpwVcPerfIntervalValidData {
          type boolean;
          description
           "This variable indicates if the data for this interval 
            is valid.";
          smiv2:max-access "read-only";
          smiv2:oid "1.3.6.1.4.1.9.10.106.1.4.1.2";
        }

        leaf cpwVcPerfIntervalTimeElapsed {
          type int32;
          description
           "The duration of a particular interval in seconds. 
            Adjustments in the system's time-of-day clock, may 
            cause the interval to be greater or less than the 
            normal value. Therefore this actual interval value 
            is provided.";
          smiv2:max-access "read-only";
          smiv2:oid "1.3.6.1.4.1.9.10.106.1.4.1.3";
        }

        leaf cpwVcPerfIntervalInHCPackets {
          type yang:counter64;
          description
           "High capacity counter for number of packets received by 
            the VC (from the PSN) in a particular 15-minute interval.";
          smiv2:max-access "read-only";
          smiv2:oid "1.3.6.1.4.1.9.10.106.1.4.1.4";
        }

        leaf cpwVcPerfIntervalInHCBytes {
          type yang:counter64;
          description
           "High capacity counter for number of bytes received by the  
            VC (from the PSN) in a particular 15-minute interval.";
          smiv2:max-access "read-only";
          smiv2:oid "1.3.6.1.4.1.9.10.106.1.4.1.5";
        }

        leaf cpwVcPerfIntervalOutHCPackets {
          type yang:counter64;
          description
           "High capacity counter for number of packets forwarded by  
            the VC (to the PSN) in a particular 15-minute interval.";
          smiv2:max-access "read-only";
          smiv2:oid "1.3.6.1.4.1.9.10.106.1.4.1.6";
        }

        leaf cpwVcPerfIntervalOutHCBytes {
          type yang:counter64;
          description
           "High capacity counter for number of bytes forwarded by the  
            VC (to the PSN) in a particular 15-minute interval.";
          smiv2:max-access "read-only";
          smiv2:oid "1.3.6.1.4.1.9.10.106.1.4.1.7";
        }
      }
    }

    container cpwVcPerfTotalTable {
      description
       "This table provides per-VC Performance information from VC  
        start time.";
      smiv2:oid "1.3.6.1.4.1.9.10.106.1.5";

      list cpwVcPerfTotalEntry {
        key "cpwVcIndex";
        description
         "An entry in this table is created agent for every VC.";
        smiv2:oid "1.3.6.1.4.1.9.10.106.1.5.1";

        leaf cpwVcIndex {
          type leafref {
            path "/cisco-ietf-pw:CISCO-IETF-PW-MIB/cisco-ietf-pw:cpwVcTable/cisco-ietf-pw:cpwVcEntry/cisco-ietf-pw:cpwVcIndex";
          }
        }

        leaf cpwVcPerfTotalInHCPackets {
          type yang:counter64;
          description
           "High capacity counter for number of packets received by the  
            VC (from the PSN).";
          smiv2:max-access "read-only";
          smiv2:oid "1.3.6.1.4.1.9.10.106.1.5.1.1";
        }

        leaf cpwVcPerfTotalInHCBytes {
          type yang:counter64;
          description
           "High capacity counter for number of bytes received by the  
            VC (from the PSN).";
          smiv2:max-access "read-only";
          smiv2:oid "1.3.6.1.4.1.9.10.106.1.5.1.2";
        }

        leaf cpwVcPerfTotalOutHCPackets {
          type yang:counter64;
          description
           "High capacity counter for number of packets forwarded by  
            the VC (to the PSN).";
          smiv2:max-access "read-only";
          smiv2:oid "1.3.6.1.4.1.9.10.106.1.5.1.3";
        }

        leaf cpwVcPerfTotalOutHCBytes {
          type yang:counter64;
          description
           "High capacity counter for number of bytes forwarded by the  
            VC (to the PSN).";
          smiv2:max-access "read-only";
          smiv2:oid "1.3.6.1.4.1.9.10.106.1.5.1.4";
        }

        leaf cpwVcPerfTotalDiscontinuityTime {
          type yang:timestamp;
          description
           "The value of sysUpTime on the most recent occasion at 
            which any one or more of this row Counter32 or 
            Counter64 suffered a discontinuity. If no such 
            discontinuities have occurred since the last re- 
            initialization of the local management subsystem, then 
            this object contains a zero value.";
          smiv2:max-access "read-only";
          smiv2:oid "1.3.6.1.4.1.9.10.106.1.5.1.5";
        }
      }
    }

    container cpwVcIdMappingTable {
      description
       "This table provides reverse mapping of the existing VCs  
        based on vc type and VC ID ordering. This table is  
        typically useful for EMS ordered query of existing VCs.";
      smiv2:oid "1.3.6.1.4.1.9.10.106.1.7";

      list cpwVcIdMappingEntry {
        key "cpwVcIdMappingVcType cpwVcIdMappingVcID cpwVcIdMappingPeerAddrType cpwVcIdMappingPeerAddr cpwVcIdMappingVcIndex";
        description
         "An entry in this table is created by the agent for every  
          VC configured by the cpwVcTable.";
        smiv2:oid "1.3.6.1.4.1.9.10.106.1.7.1";

        leaf cpwVcIdMappingVcType {
          type cisco-ietf:CpwVcType;
          description
           "The VC type (indicate the service) of this VC.";
          smiv2:max-access "not-accessible";
          smiv2:oid "1.3.6.1.4.1.9.10.106.1.7.1.1";
        }

        leaf cpwVcIdMappingVcID {
          type cisco-ietf:CpwVcIDType;
          description
           "The VC ID of this VC. Zero if the VC is configured  
            manually.";
          smiv2:max-access "not-accessible";
          smiv2:oid "1.3.6.1.4.1.9.10.106.1.7.1.2";
        }

        leaf cpwVcIdMappingPeerAddrType {
          type inet-address:InetAddressType;
          description
           "IP address type of the peer node.";
          smiv2:max-access "not-accessible";
          smiv2:oid "1.3.6.1.4.1.9.10.106.1.7.1.3";
        }

        leaf cpwVcIdMappingPeerAddr {
          type inet-address:InetAddress;
          description
           "IP address type of the peer node.";
          smiv2:max-access "not-accessible";
          smiv2:oid "1.3.6.1.4.1.9.10.106.1.7.1.4";
        }

        leaf cpwVcIdMappingVcIndex {
          type cisco-ietf:CpwVcIndexType;
          description
           "The value that represent the VC in the cpwVcTable.";
          smiv2:max-access "read-only";
          smiv2:oid "1.3.6.1.4.1.9.10.106.1.7.1.5";
        }
      }
    }

    container cpwVcPeerMappingTable {
      description
       "This table provides reverse mapping of the existing VCs  
        based on vc type and VC ID ordering. This table is  
        typically useful for EMS ordered query of existing VCs.";
      smiv2:oid "1.3.6.1.4.1.9.10.106.1.8";

      list cpwVcPeerMappingEntry {
        key "cpwVcPeerMappingPeerAddrType cpwVcPeerMappingPeerAddr cpwVcPeerMappingVcType cpwVcPeerMappingVcID cpwVcPeerMappingVcIndex";
        description
         "An entry in this table is created by the agent for every  
          VC configured in cpwVcTable.";
        smiv2:oid "1.3.6.1.4.1.9.10.106.1.8.1";

        leaf cpwVcPeerMappingPeerAddrType {
          type inet-address:InetAddressType;
          description
           "IP address type of the peer node.";
          smiv2:max-access "not-accessible";
          smiv2:oid "1.3.6.1.4.1.9.10.106.1.8.1.1";
        }

        leaf cpwVcPeerMappingPeerAddr {
          type inet-address:InetAddress;
          description
           "IP address type of the peer node.";
          smiv2:max-access "not-accessible";
          smiv2:oid "1.3.6.1.4.1.9.10.106.1.8.1.2";
        }

        leaf cpwVcPeerMappingVcType {
          type cisco-ietf:CpwVcType;
          description
           "The VC type (indicate the service) of this VC.";
          smiv2:max-access "not-accessible";
          smiv2:oid "1.3.6.1.4.1.9.10.106.1.8.1.3";
        }

        leaf cpwVcPeerMappingVcID {
          type cisco-ietf:CpwVcIDType;
          description
           "The VC ID of this VC. Zero if the VC is configured  
            manually.";
          smiv2:max-access "not-accessible";
          smiv2:oid "1.3.6.1.4.1.9.10.106.1.8.1.4";
        }

        leaf cpwVcPeerMappingVcIndex {
          type cisco-ietf:CpwVcIndexType;
          description
           "The value that represent the VC in the cpwVcTable.";
          smiv2:max-access "read-only";
          smiv2:oid "1.3.6.1.4.1.9.10.106.1.8.1.5";
        }
      }
    }
  }

  notification cpwVcDown {
    description
     "This notification is generated when the
      cpwVcOperStatus object for one or more contiguous
      entries in cpwVcTable are about to enter the
      down(2) state from some other state. The included values
      of cpwVcOperStatus MUST all be set equal to this
      down(2) state.  The two instances of cpwVcOperStatus
      in this notification indicate the range of indexes
      that are affected.  Note that all the indexes of the
      two ends of the range can be derived from the
      instance identifiers of these two objects.  For
      cases where a contiguous range of cross-connects
      have transitioned into the down(2) state at roughly
      the same time, the device SHOULD issue a single
      notification for each range of contiguous indexes in
      an effort to minimize the emission of a large number
      of notifications.  If a notification has to be
      issued for just a single cross-connect entry, then
      the instance identifier (and values) of the two
      cpwVcOperStatus objects MUST be identical.";
    smiv2:oid "1.3.6.1.4.1.9.10.106.2.1";

    container object-1 {

      leaf cpwVcIndex {
        type leafref {
          path "/cisco-ietf-pw:CISCO-IETF-PW-MIB/cisco-ietf-pw:cpwVcTable/cisco-ietf-pw:cpwVcEntry/cisco-ietf-pw:cpwVcIndex";
        }
      }

      leaf cpwVcOperStatus {
        type leafref {
          path "/cisco-ietf-pw:CISCO-IETF-PW-MIB/cisco-ietf-pw:cpwVcTable/cisco-ietf-pw:cpwVcEntry/cisco-ietf-pw:cpwVcOperStatus";
        }
      }
    }

    container object-2 {

      leaf cpwVcIndex {
        type leafref {
          path "/cisco-ietf-pw:CISCO-IETF-PW-MIB/cisco-ietf-pw:cpwVcTable/cisco-ietf-pw:cpwVcEntry/cisco-ietf-pw:cpwVcIndex";
        }
      }

      leaf cpwVcOperStatus {
        type leafref {
          path "/cisco-ietf-pw:CISCO-IETF-PW-MIB/cisco-ietf-pw:cpwVcTable/cisco-ietf-pw:cpwVcEntry/cisco-ietf-pw:cpwVcOperStatus";
        }
      }
    }
  }

  notification cpwVcUp {
    description
     "This notification is generated when the
      cpwVcOperStatus object for one or more contiguous
      entries in cpwVcTable are about to enter the up(1)
      state from some other state. The included values of
      cpwVcOperStatus MUST both be set equal to this
      new state (i.e: up(1)).  The two instances of 
      cpwVcOperStatus in this notification indicate the range 
      of indexes that are affected.  Note that all the indexes 
      of the two ends of the range can be derived from the
      instance identifiers of these two objects.  For
      cases where a contiguous range of cross-connects
      have transitioned into the up(1) state at roughly
      the same time, the device SHOULD issue a single
      notification for each range of contiguous indexes in
      an effort to minimize the emission of a large number
      of notifications.  If a notification has to be
      issued for just a single cross-connect entry, then
      the instance identifier (and values) of the two
      cpwVcOperStatus objects MUST be the identical.";
    smiv2:oid "1.3.6.1.4.1.9.10.106.2.2";

    container object-1 {

      leaf cpwVcIndex {
        type leafref {
          path "/cisco-ietf-pw:CISCO-IETF-PW-MIB/cisco-ietf-pw:cpwVcTable/cisco-ietf-pw:cpwVcEntry/cisco-ietf-pw:cpwVcIndex";
        }
      }

      leaf cpwVcOperStatus {
        type leafref {
          path "/cisco-ietf-pw:CISCO-IETF-PW-MIB/cisco-ietf-pw:cpwVcTable/cisco-ietf-pw:cpwVcEntry/cisco-ietf-pw:cpwVcOperStatus";
        }
      }
    }

    container object-2 {

      leaf cpwVcIndex {
        type leafref {
          path "/cisco-ietf-pw:CISCO-IETF-PW-MIB/cisco-ietf-pw:cpwVcTable/cisco-ietf-pw:cpwVcEntry/cisco-ietf-pw:cpwVcIndex";
        }
      }

      leaf cpwVcOperStatus {
        type leafref {
          path "/cisco-ietf-pw:CISCO-IETF-PW-MIB/cisco-ietf-pw:cpwVcTable/cisco-ietf-pw:cpwVcEntry/cisco-ietf-pw:cpwVcOperStatus";
        }
      }
    }
  }

  smiv2:alias "cpwVcMIB" {
    smiv2:oid "1.3.6.1.4.1.9.10.106";
  }

  smiv2:alias "cpwVcObjects" {
    smiv2:oid "1.3.6.1.4.1.9.10.106.1";
  }

  smiv2:alias "cpwVcNotifications" {
    smiv2:oid "1.3.6.1.4.1.9.10.106.2";
  }

  smiv2:alias "cpwVcConformance" {
    smiv2:oid "1.3.6.1.4.1.9.10.106.3";
  }

  smiv2:alias "cpwVcGroups" {
    smiv2:oid "1.3.6.1.4.1.9.10.106.3.1";
  }

  smiv2:alias "cpwVcCompliances" {
    smiv2:oid "1.3.6.1.4.1.9.10.106.3.2";
  }

}
