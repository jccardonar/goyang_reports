/*
 * This YANG module has been generated by smidump 0.5.0:
 *
 *      smidump -f yang CISCO-SMI
 *
 * Do not edit. Edit the source file instead!
 */

module CISCO-SMI {

  namespace "urn:ietf:params:xml:ns:yang:smiv2:CISCO-SMI";
  prefix "cisco-smi";

  import ietf-yang-smiv2 {
    prefix "smiv2";
  }

  organization
   "Cisco Systems, Inc.";

  contact
   "Cisco Systems
    Customer Service
    
    Postal: 170 West Tasman Drive
    San Jose, CA  95134
    USA
    
    Tel: +1 800 553-NETS
    
    E-mail: cs-snmp@cisco.com";

  description
   "The Structure of Management Information for the
    Cisco enterprise.";

  revision 2012-08-29 {
    description
     "Added ciscoSMB under otherEnterprises";
  }

  revision 2009-02-03 {
    description
     "Added ciscoSB under otherEnterprises";
  }

  revision 2002-03-21 {
    description
     "Added ciscoPKI for PKI policy and extension OIDs";
  }

  revision 2001-05-22 {
    description
     "Added transport protocol domains.";
  }

  revision 2000-11-01 {
    description
     "Added ciscoDomains to define new transports.  Also added
      ciscoCpeCIB, which will contain managed objects that
      contribute to the CPE Configuration Information Base (CIB).";
  }

  revision 2000-01-11 {
    description
     "Added ciscoPolicy, ciscoPolicyAuto, ciscoPIB, and
      ciscoPibToMib.";
  }

  revision 1997-04-09 {
    description
     "Added ciscoPartnerProducts to generate sysObjectID
      for partner platforms";
  }

  revision 1995-05-16 {
    description
     "New oid assignments for Cisco REPEATER MIB and others.";
  }

  revision 1994-04-26 {
    description
     "Initial version of this MIB module.";
  }

  identity ciscoProducts {
    base smiv2:object-identity;
    description
     "ciscoProducts is the root OBJECT IDENTIFIER from
      which sysObjectID values are assigned.  Actual
      values are defined in CISCO-PRODUCTS-MIB.";
    smiv2:oid "1.3.6.1.4.1.9.1";
  }

  identity local {
    base smiv2:object-identity;
    description
     "Subtree beneath which pre-10.2 MIBS were built.";
    smiv2:oid "1.3.6.1.4.1.9.2";
  }

  identity temporary {
    base smiv2:object-identity;
    description
     "Subtree beneath which pre-10.2 experiments were
      placed.";
    smiv2:oid "1.3.6.1.4.1.9.3";
  }

  identity pakmon {
    base smiv2:object-identity;
    description
     "reserved for pakmon";
    smiv2:oid "1.3.6.1.4.1.9.4";
  }

  identity workgroup {
    base smiv2:object-identity;
    description
     "subtree reserved for use by the Workgroup Business Unit";
    smiv2:oid "1.3.6.1.4.1.9.5";
  }

  identity otherEnterprises {
    base smiv2:object-identity;
    description
     "otherEnterprises provides a root object identifier
      from which mibs produced by other companies may be
      placed.  mibs produced by other enterprises are
      typicially implemented with the object identifiers
      as defined in the mib, but if the mib is deemed to
      be uncontrolled, we may reroot the mib at this
      subtree in order to have a controlled version.";
    smiv2:oid "1.3.6.1.4.1.9.6";
  }

  identity ciscoSB {
    base smiv2:object-identity;
    description
     "ciscoSB provides root Object Identifier for Management
      Information Base for products of Cisco Small Business.
      This includes products rebranded from linksys aquisition.
      MIB numbers under this root are managed and controlled
      by ciscosb_mib@cisco.com.";
    smiv2:oid "1.3.6.1.4.1.9.6.1";
  }

  identity ciscoSMB {
    base smiv2:object-identity;
    description
     "ciscoSMB provides root Object Identifier for Management
      Information Base for products of Cisco built for Small and 
      Medium Business market.The MIB numbers under this root are 
      managed and controlled by ciscosmb_mib@cisco.com";
    smiv2:oid "1.3.6.1.4.1.9.6.2";
  }

  identity ciscoAgentCapability {
    base smiv2:object-identity;
    description
     "ciscoAgentCapability provides a root object identifier
      from which AGENT-CAPABILITIES values may be assigned.";
    smiv2:oid "1.3.6.1.4.1.9.7";
  }

  identity ciscoConfig {
    base smiv2:object-identity;
    description
     "ciscoConfig is the main subtree for configuration mibs.";
    smiv2:oid "1.3.6.1.4.1.9.8";
  }

  identity ciscoMgmt {
    base smiv2:object-identity;
    description
     "ciscoMgmt is the main subtree for new mib development.";
    smiv2:oid "1.3.6.1.4.1.9.9";
  }

  identity ciscoExperiment {
    base smiv2:object-identity;
    description
     "ciscoExperiment provides a root object identifier
      from which experimental mibs may be temporarily
      based.  mibs are typicially based here if they
      fall in one of two categories
      1) are IETF work-in-process mibs which have not
      been assigned a permanent object identifier by
      the IANA.
      2) are cisco work-in-process which has not been
      assigned a permanent object identifier by the
      cisco assigned number authority, typicially because
      the mib is not ready for deployment.
      
      NOTE WELL:  support for mibs in the ciscoExperiment
      subtree will be deleted when a permanent object
      identifier assignment is made.";
    smiv2:oid "1.3.6.1.4.1.9.10";
  }

  identity ciscoAdmin {
    base smiv2:object-identity;
    description
     "ciscoAdmin is reserved for administratively assigned
      OBJECT IDENTIFIERS, i.e. those not associated with MIB
      objects";
    smiv2:oid "1.3.6.1.4.1.9.11";
  }

  identity ciscoProxy {
    base smiv2:object-identity;
    description
     "ciscoProxy OBJECT IDENTIFIERS are used to uniquely name
      party mib records created to proxy for SNMPv1.";
    smiv2:oid "1.3.6.1.4.1.9.11.1";
  }

  identity ciscoRptrGroupObjectID {
    base smiv2:object-identity;
    description
     "ciscoRptrGroupObjectID OBJECT IDENTIFIERS are used to
      uniquely identify groups of repeater ports for use by the
      SNMP-REPEATER-MIB (RFC 1516) rptrGroupObjectID object.";
    smiv2:oid "1.3.6.1.4.1.9.11.2";
  }

  identity ciscoUnknownRptrGroup {
    base smiv2:object-identity;
    description
     "The identity of an unknown repeater port group.";
    smiv2:oid "1.3.6.1.4.1.9.11.2.1";
  }

  identity cisco2505RptrGroup {
    base smiv2:object-identity;
    description
     "The authoritative identity of the Cisco 2505 repeater
      port group.";
    smiv2:oid "1.3.6.1.4.1.9.11.2.2";
  }

  identity cisco2507RptrGroup {
    base smiv2:object-identity;
    description
     "The authoritative identity of the Cisco 2507 repeater
      port group.";
    smiv2:oid "1.3.6.1.4.1.9.11.2.3";
  }

  identity cisco2516RptrGroup {
    base smiv2:object-identity;
    description
     "The authoritative identity of the Cisco 2516 repeater
      port group.";
    smiv2:oid "1.3.6.1.4.1.9.11.2.4";
  }

  identity ciscoWsx5020RptrGroup {
    base smiv2:object-identity;
    description
     "The authoritative identity of the wsx5020 repeater
      port group.";
    smiv2:oid "1.3.6.1.4.1.9.11.2.5";
  }

  identity ciscoChipSets {
    base smiv2:object-identity;
    description
     "Numerous media-specific MIBS have an object, defined as
      an OBJECT IDENTIFIER, which is the identity of the chipset
      realizing the interface.  Cisco-specific chipsets have their 
      OBJECT IDENTIFIERS assigned under this subtree.";
    smiv2:oid "1.3.6.1.4.1.9.11.3";
  }

  identity ciscoChipSetSaint1 {
    base smiv2:object-identity;
    description
     "The identity of the Rev 1 SAINT ethernet chipset
      manufactured for cisco by LSI Logic.";
    smiv2:oid "1.3.6.1.4.1.9.11.3.1";
  }

  identity ciscoChipSetSaint2 {
    base smiv2:object-identity;
    description
     "The identity of the Rev 2 SAINT ethernet chipset
      manufactured for cisco by LSI Logic.";
    smiv2:oid "1.3.6.1.4.1.9.11.3.2";
  }

  identity ciscoChipSetSaint3 {
    base smiv2:object-identity;
    description
     "The identity of the Rev 3 SAINT ethernet chipset
      manufactured for cisco by Plessey.";
    smiv2:oid "1.3.6.1.4.1.9.11.3.3";
  }

  identity ciscoChipSetSaint4 {
    base smiv2:object-identity;
    description
     "The identity of the Rev 4 SAINT ethernet chipset
      manufactured for cisco by Mitsubishi.";
    smiv2:oid "1.3.6.1.4.1.9.11.3.4";
  }

  identity ciscoModules {
    base smiv2:object-identity;
    description
     "ciscoModules provides a root object identifier
      from which MODULE-IDENTITY values may be assigned.";
    smiv2:oid "1.3.6.1.4.1.9.12";
  }

  identity lightstream {
    base smiv2:object-identity;
    description
     "subtree reserved for use by Lightstream";
    smiv2:oid "1.3.6.1.4.1.9.13";
  }

  identity ciscoworks {
    base smiv2:object-identity;
    description
     "ciscoworks provides a root object identifier beneath
      which mibs applicable to the CiscoWorks family of network
      management products are defined.";
    smiv2:oid "1.3.6.1.4.1.9.14";
  }

  identity newport {
    base smiv2:object-identity;
    description
     "subtree reserved for use by the former Newport Systems
      Solutions, now a portion of the Access Business Unit.";
    smiv2:oid "1.3.6.1.4.1.9.15";
  }

  identity ciscoPartnerProducts {
    base smiv2:object-identity;
    description
     "ciscoPartnerProducts is the root OBJECT IDENTIFIER from
      which partner sysObjectID values may be assigned. Such 
      sysObjectID values are composed of the ciscoPartnerProducts
      prefix, followed by a single identifier that is unique for 
      each partner, followed by the value of sysObjectID of the
      Cisco product from which partner product is derived.  Note
      that the chassisPartner MIB object defines the value of the
      identifier assigned to each partner.";
    smiv2:oid "1.3.6.1.4.1.9.16";
  }

  identity ciscoPolicy {
    base smiv2:object-identity;
    description
     "ciscoPolicy is the root of the Cisco-assigned OID
      subtree for use with Policy Management.";
    smiv2:oid "1.3.6.1.4.1.9.17";
  }

  identity ciscoPIB {
    base smiv2:object-identity;
    description
     "ciscoPIB is the root of the Cisco-assigned OID
      subtree for assignment to PIB (Policy Information
      Base) modules.";
    smiv2:oid "1.3.6.1.4.1.9.17.2";
  }

  identity ciscoPolicyAuto {
    base smiv2:object-identity;
    description
     "ciscoPolicyAuto is the root of the Cisco-assigned
      OID subtree for OIDs which are automatically assigned
      for use in Policy Management.";
    smiv2:oid "1.3.6.1.4.1.9.18";
  }

  identity ciscoPibToMib {
    base smiv2:object-identity;
    description
     "ciscoPibToMib is the root of the Cisco-assigned
      OID subtree for MIBs which are algorithmically
      generated/translated from Cisco PIBs with OIDs
      assigned under the ciscoPIB subtree.
      These generated MIBs allow management
      entities (other the current Policy Server) to
      read the downloaded policy.  By convention, for PIB
      'ciscoPIB.x', the generated MIB shall have the
      name 'ciscoPibToMib.x'.";
    smiv2:oid "1.3.6.1.4.1.9.18.2";
  }

  identity ciscoDomains {
    base smiv2:object-identity;
    description
     "ciscoDomains provides a root object identifier from which
      different transport mapping values may be assigned.";
    smiv2:oid "1.3.6.1.4.1.9.19";
  }

  identity ciscoTDomainUdpIpv4 {
    base smiv2:object-identity;
    description
     "The UDP over IPv4 transport domain.  The corresponding
      transport address is of type CiscoTAddressIPv4.";
    smiv2:oid "1.3.6.1.4.1.9.19.99999.1";
  }

  identity ciscoTDomainUdpIpv6 {
    base smiv2:object-identity;
    description
     "The UDP over IPv6 transport domain.  The corresponding
      transport address is of type CiscoTAddressIPv6 for global IPv6
      addresses and CiscoTAddressIPv6s for scoped IPv6 addresses.";
    smiv2:oid "1.3.6.1.4.1.9.19.99999.2";
  }

  identity ciscoTDomainTcpIpv4 {
    base smiv2:object-identity;
    description
     "The TCP over IPv4 transport domain.  The corresponding
      transport address is of type CiscoTAddressIPv4.";
    smiv2:oid "1.3.6.1.4.1.9.19.99999.3";
  }

  identity ciscoTDomainTcpIpv6 {
    base smiv2:object-identity;
    description
     "The TCP over IPv6 transport domain.  The corresponding
      transport address is of type CiscoTAddressIPv6 for global IPv6
      addresses and CiscoTAddressIPv6s for scoped IPv6 addresses.";
    smiv2:oid "1.3.6.1.4.1.9.19.99999.4";
  }

  identity ciscoTDomainLocal {
    base smiv2:object-identity;
    description
     "The Posix Local IPC transport domain. The corresponding
      transport address is of type CiscoTAddressLocal.  The Posix
      Local IPC transport domain incorporates the well known UNIX
      domain sockets.";
    smiv2:oid "1.3.6.1.4.1.9.19.99999.5";
  }

  identity ciscoTDomainClns {
    base smiv2:object-identity;
    description
     "The CLNS transport domain.  The corresponding transport
      address is of type CiscoTAddressOSI.";
    smiv2:oid "1.3.6.1.4.1.9.19.99999.6";
  }

  identity ciscoTDomainCons {
    base smiv2:object-identity;
    description
     "The CONS transport domain.  The corresponding transport
      address is of type CiscoTAddressOSI.";
    smiv2:oid "1.3.6.1.4.1.9.19.99999.7";
  }

  identity ciscoTDomainDdp {
    base smiv2:object-identity;
    description
     "The DDP transport domain.  The corresponding transport
      address is of type CiscoTAddressNBP.";
    smiv2:oid "1.3.6.1.4.1.9.19.99999.8";
  }

  identity ciscoTDomainIpx {
    base smiv2:object-identity;
    description
     "The IPX transport domain.  The corresponding transport
      address is of type CiscoTAddressIPX.";
    smiv2:oid "1.3.6.1.4.1.9.19.99999.9";
  }

  identity ciscoTDomainSctpIpv4 {
    base smiv2:object-identity;
    description
     "The SCTP over IPv4 transport domain.  The corresponding
      transport address is of type CiscoTAddressIPv4.";
    reference
     "RFC 2960 - Stream Control Transmission Protocol. R. Stewart,
      Q. Xie, K. Morneault, C. Sharp, H. Schwarzbauer, T. Taylor,
      I. Rytina, M. Kalla, L. Zhang, V. Paxson. October 2000.";
    smiv2:oid "1.3.6.1.4.1.9.19.99999.10";
  }

  identity ciscoTDomainSctpIpv6 {
    base smiv2:object-identity;
    description
     "The SCTP over IPv6 transport domain.  The corresponding
      transport address is of type CiscoTAddressIPv6 for global IPv6
      addresses and CiscoTAddressIPv6s for scoped IPv6 addresses.";
    reference
     "RFC 2960 - Stream Control Transmission Protocol. R. Stewart,
      Q. Xie, K. Morneault, C. Sharp, H. Schwarzbauer, T. Taylor,
      I. Rytina, M. Kalla, L. Zhang, V. Paxson. October 2000.";
    smiv2:oid "1.3.6.1.4.1.9.19.99999.11";
  }

  identity ciscoCIB {
    base smiv2:object-identity;
    description
     "ciscoCIB is the root of the Cisco-assigned OID subtree for
      assignment to MIB modules describing managed objects that
      part of the CPE automatic configuration framework.";
    smiv2:oid "1.3.6.1.4.1.9.20";
  }

  identity ciscoCibMmiGroup {
    base smiv2:object-identity;
    description
     "ciscoCibMmiGroup is the root of the Cisco-assigned OID
      subtree for assignment to MIB modules describing managed
      objects supporting the Modem Management Interface (MMI),
      the interface that facilitates CPE automatic configuration.";
    smiv2:oid "1.3.6.1.4.1.9.20.1";
  }

  identity ciscoCibProvGroup {
    base smiv2:object-identity;
    description
     "ciscoCibStoreGroup is the root of the Cisco-assigned OID
      subtree for assignment to MIB modules describing managed
      objects contributing to the Configuration Information Base
      (CIB).";
    smiv2:oid "1.3.6.1.4.1.9.20.2";
  }

  identity ciscoPKI {
    base smiv2:object-identity;
    description
     "ciscoPKI is the root of cisco-assigned OID subtree for PKI
      Certificate Policies and Certificate Extensions.";
    smiv2:oid "1.3.6.1.4.1.9.21";
  }

  smiv2:alias "cisco" {
    smiv2:oid "1.3.6.1.4.1.9";
  }

  smiv2:alias "ciscoProducts" {
    description
     "ciscoProducts is the root OBJECT IDENTIFIER from
      which sysObjectID values are assigned.  Actual
      values are defined in CISCO-PRODUCTS-MIB.";
    smiv2:oid "1.3.6.1.4.1.9.1";
  }

  smiv2:alias "local" {
    description
     "Subtree beneath which pre-10.2 MIBS were built.";
    smiv2:oid "1.3.6.1.4.1.9.2";
  }

  smiv2:alias "temporary" {
    description
     "Subtree beneath which pre-10.2 experiments were
      placed.";
    smiv2:oid "1.3.6.1.4.1.9.3";
  }

  smiv2:alias "pakmon" {
    description
     "reserved for pakmon";
    smiv2:oid "1.3.6.1.4.1.9.4";
  }

  smiv2:alias "workgroup" {
    description
     "subtree reserved for use by the Workgroup Business Unit";
    smiv2:oid "1.3.6.1.4.1.9.5";
  }

  smiv2:alias "otherEnterprises" {
    description
     "otherEnterprises provides a root object identifier
      from which mibs produced by other companies may be
      placed.  mibs produced by other enterprises are
      typicially implemented with the object identifiers
      as defined in the mib, but if the mib is deemed to
      be uncontrolled, we may reroot the mib at this
      subtree in order to have a controlled version.";
    smiv2:oid "1.3.6.1.4.1.9.6";
  }

  smiv2:alias "ciscoSB" {
    description
     "ciscoSB provides root Object Identifier for Management
      Information Base for products of Cisco Small Business.
      This includes products rebranded from linksys aquisition.
      MIB numbers under this root are managed and controlled
      by ciscosb_mib@cisco.com.";
    smiv2:oid "1.3.6.1.4.1.9.6.1";
  }

  smiv2:alias "ciscoSMB" {
    description
     "ciscoSMB provides root Object Identifier for Management
      Information Base for products of Cisco built for Small and 
      Medium Business market.The MIB numbers under this root are 
      managed and controlled by ciscosmb_mib@cisco.com";
    smiv2:oid "1.3.6.1.4.1.9.6.2";
  }

  smiv2:alias "ciscoAgentCapability" {
    description
     "ciscoAgentCapability provides a root object identifier
      from which AGENT-CAPABILITIES values may be assigned.";
    smiv2:oid "1.3.6.1.4.1.9.7";
  }

  smiv2:alias "ciscoConfig" {
    description
     "ciscoConfig is the main subtree for configuration mibs.";
    smiv2:oid "1.3.6.1.4.1.9.8";
  }

  smiv2:alias "ciscoMgmt" {
    description
     "ciscoMgmt is the main subtree for new mib development.";
    smiv2:oid "1.3.6.1.4.1.9.9";
  }

  smiv2:alias "ciscoExperiment" {
    description
     "ciscoExperiment provides a root object identifier
      from which experimental mibs may be temporarily
      based.  mibs are typicially based here if they
      fall in one of two categories
      1) are IETF work-in-process mibs which have not
      been assigned a permanent object identifier by
      the IANA.
      2) are cisco work-in-process which has not been
      assigned a permanent object identifier by the
      cisco assigned number authority, typicially because
      the mib is not ready for deployment.
      
      NOTE WELL:  support for mibs in the ciscoExperiment
      subtree will be deleted when a permanent object
      identifier assignment is made.";
    smiv2:oid "1.3.6.1.4.1.9.10";
  }

  smiv2:alias "ciscoAdmin" {
    description
     "ciscoAdmin is reserved for administratively assigned
      OBJECT IDENTIFIERS, i.e. those not associated with MIB
      objects";
    smiv2:oid "1.3.6.1.4.1.9.11";
  }

  smiv2:alias "ciscoProxy" {
    description
     "ciscoProxy OBJECT IDENTIFIERS are used to uniquely name
      party mib records created to proxy for SNMPv1.";
    smiv2:oid "1.3.6.1.4.1.9.11.1";
  }

  smiv2:alias "ciscoPartyProxy" {
    smiv2:oid "1.3.6.1.4.1.9.11.1.1";
  }

  smiv2:alias "ciscoContextProxy" {
    smiv2:oid "1.3.6.1.4.1.9.11.1.2";
  }

  smiv2:alias "ciscoRptrGroupObjectID" {
    description
     "ciscoRptrGroupObjectID OBJECT IDENTIFIERS are used to
      uniquely identify groups of repeater ports for use by the
      SNMP-REPEATER-MIB (RFC 1516) rptrGroupObjectID object.";
    smiv2:oid "1.3.6.1.4.1.9.11.2";
  }

  smiv2:alias "ciscoUnknownRptrGroup" {
    description
     "The identity of an unknown repeater port group.";
    smiv2:oid "1.3.6.1.4.1.9.11.2.1";
  }

  smiv2:alias "cisco2505RptrGroup" {
    description
     "The authoritative identity of the Cisco 2505 repeater
      port group.";
    smiv2:oid "1.3.6.1.4.1.9.11.2.2";
  }

  smiv2:alias "cisco2507RptrGroup" {
    description
     "The authoritative identity of the Cisco 2507 repeater
      port group.";
    smiv2:oid "1.3.6.1.4.1.9.11.2.3";
  }

  smiv2:alias "cisco2516RptrGroup" {
    description
     "The authoritative identity of the Cisco 2516 repeater
      port group.";
    smiv2:oid "1.3.6.1.4.1.9.11.2.4";
  }

  smiv2:alias "ciscoWsx5020RptrGroup" {
    description
     "The authoritative identity of the wsx5020 repeater
      port group.";
    smiv2:oid "1.3.6.1.4.1.9.11.2.5";
  }

  smiv2:alias "ciscoChipSets" {
    description
     "Numerous media-specific MIBS have an object, defined as
      an OBJECT IDENTIFIER, which is the identity of the chipset
      realizing the interface.  Cisco-specific chipsets have their 
      OBJECT IDENTIFIERS assigned under this subtree.";
    smiv2:oid "1.3.6.1.4.1.9.11.3";
  }

  smiv2:alias "ciscoChipSetSaint1" {
    description
     "The identity of the Rev 1 SAINT ethernet chipset
      manufactured for cisco by LSI Logic.";
    smiv2:oid "1.3.6.1.4.1.9.11.3.1";
  }

  smiv2:alias "ciscoChipSetSaint2" {
    description
     "The identity of the Rev 2 SAINT ethernet chipset
      manufactured for cisco by LSI Logic.";
    smiv2:oid "1.3.6.1.4.1.9.11.3.2";
  }

  smiv2:alias "ciscoChipSetSaint3" {
    description
     "The identity of the Rev 3 SAINT ethernet chipset
      manufactured for cisco by Plessey.";
    smiv2:oid "1.3.6.1.4.1.9.11.3.3";
  }

  smiv2:alias "ciscoChipSetSaint4" {
    description
     "The identity of the Rev 4 SAINT ethernet chipset
      manufactured for cisco by Mitsubishi.";
    smiv2:oid "1.3.6.1.4.1.9.11.3.4";
  }

  smiv2:alias "ciscoModules" {
    description
     "ciscoModules provides a root object identifier
      from which MODULE-IDENTITY values may be assigned.";
    smiv2:oid "1.3.6.1.4.1.9.12";
  }

  smiv2:alias "lightstream" {
    description
     "subtree reserved for use by Lightstream";
    smiv2:oid "1.3.6.1.4.1.9.13";
  }

  smiv2:alias "ciscoworks" {
    description
     "ciscoworks provides a root object identifier beneath
      which mibs applicable to the CiscoWorks family of network
      management products are defined.";
    smiv2:oid "1.3.6.1.4.1.9.14";
  }

  smiv2:alias "newport" {
    description
     "subtree reserved for use by the former Newport Systems
      Solutions, now a portion of the Access Business Unit.";
    smiv2:oid "1.3.6.1.4.1.9.15";
  }

  smiv2:alias "ciscoPartnerProducts" {
    description
     "ciscoPartnerProducts is the root OBJECT IDENTIFIER from
      which partner sysObjectID values may be assigned. Such 
      sysObjectID values are composed of the ciscoPartnerProducts
      prefix, followed by a single identifier that is unique for 
      each partner, followed by the value of sysObjectID of the
      Cisco product from which partner product is derived.  Note
      that the chassisPartner MIB object defines the value of the
      identifier assigned to each partner.";
    smiv2:oid "1.3.6.1.4.1.9.16";
  }

  smiv2:alias "ciscoPolicy" {
    description
     "ciscoPolicy is the root of the Cisco-assigned OID
      subtree for use with Policy Management.";
    smiv2:oid "1.3.6.1.4.1.9.17";
  }

  smiv2:alias "ciscoPIB" {
    description
     "ciscoPIB is the root of the Cisco-assigned OID
      subtree for assignment to PIB (Policy Information
      Base) modules.";
    smiv2:oid "1.3.6.1.4.1.9.17.2";
  }

  smiv2:alias "ciscoPolicyAuto" {
    description
     "ciscoPolicyAuto is the root of the Cisco-assigned
      OID subtree for OIDs which are automatically assigned
      for use in Policy Management.";
    smiv2:oid "1.3.6.1.4.1.9.18";
  }

  smiv2:alias "ciscoPibToMib" {
    description
     "ciscoPibToMib is the root of the Cisco-assigned
      OID subtree for MIBs which are algorithmically
      generated/translated from Cisco PIBs with OIDs
      assigned under the ciscoPIB subtree.
      These generated MIBs allow management
      entities (other the current Policy Server) to
      read the downloaded policy.  By convention, for PIB
      'ciscoPIB.x', the generated MIB shall have the
      name 'ciscoPibToMib.x'.";
    smiv2:oid "1.3.6.1.4.1.9.18.2";
  }

  smiv2:alias "ciscoDomains" {
    description
     "ciscoDomains provides a root object identifier from which
      different transport mapping values may be assigned.";
    smiv2:oid "1.3.6.1.4.1.9.19";
  }

  smiv2:alias "ciscoTDomains" {
    smiv2:oid "1.3.6.1.4.1.9.19.99999";
  }

  smiv2:alias "ciscoTDomainUdpIpv4" {
    description
     "The UDP over IPv4 transport domain.  The corresponding
      transport address is of type CiscoTAddressIPv4.";
    smiv2:oid "1.3.6.1.4.1.9.19.99999.1";
  }

  smiv2:alias "ciscoTDomainUdpIpv6" {
    description
     "The UDP over IPv6 transport domain.  The corresponding
      transport address is of type CiscoTAddressIPv6 for global IPv6
      addresses and CiscoTAddressIPv6s for scoped IPv6 addresses.";
    smiv2:oid "1.3.6.1.4.1.9.19.99999.2";
  }

  smiv2:alias "ciscoTDomainTcpIpv4" {
    description
     "The TCP over IPv4 transport domain.  The corresponding
      transport address is of type CiscoTAddressIPv4.";
    smiv2:oid "1.3.6.1.4.1.9.19.99999.3";
  }

  smiv2:alias "ciscoTDomainTcpIpv6" {
    description
     "The TCP over IPv6 transport domain.  The corresponding
      transport address is of type CiscoTAddressIPv6 for global IPv6
      addresses and CiscoTAddressIPv6s for scoped IPv6 addresses.";
    smiv2:oid "1.3.6.1.4.1.9.19.99999.4";
  }

  smiv2:alias "ciscoTDomainLocal" {
    description
     "The Posix Local IPC transport domain. The corresponding
      transport address is of type CiscoTAddressLocal.  The Posix
      Local IPC transport domain incorporates the well known UNIX
      domain sockets.";
    smiv2:oid "1.3.6.1.4.1.9.19.99999.5";
  }

  smiv2:alias "ciscoTDomainClns" {
    description
     "The CLNS transport domain.  The corresponding transport
      address is of type CiscoTAddressOSI.";
    smiv2:oid "1.3.6.1.4.1.9.19.99999.6";
  }

  smiv2:alias "ciscoTDomainCons" {
    description
     "The CONS transport domain.  The corresponding transport
      address is of type CiscoTAddressOSI.";
    smiv2:oid "1.3.6.1.4.1.9.19.99999.7";
  }

  smiv2:alias "ciscoTDomainDdp" {
    description
     "The DDP transport domain.  The corresponding transport
      address is of type CiscoTAddressNBP.";
    smiv2:oid "1.3.6.1.4.1.9.19.99999.8";
  }

  smiv2:alias "ciscoTDomainIpx" {
    description
     "The IPX transport domain.  The corresponding transport
      address is of type CiscoTAddressIPX.";
    smiv2:oid "1.3.6.1.4.1.9.19.99999.9";
  }

  smiv2:alias "ciscoTDomainSctpIpv4" {
    description
     "The SCTP over IPv4 transport domain.  The corresponding
      transport address is of type CiscoTAddressIPv4.";
    reference
     "RFC 2960 - Stream Control Transmission Protocol. R. Stewart,
      Q. Xie, K. Morneault, C. Sharp, H. Schwarzbauer, T. Taylor,
      I. Rytina, M. Kalla, L. Zhang, V. Paxson. October 2000.";
    smiv2:oid "1.3.6.1.4.1.9.19.99999.10";
  }

  smiv2:alias "ciscoTDomainSctpIpv6" {
    description
     "The SCTP over IPv6 transport domain.  The corresponding
      transport address is of type CiscoTAddressIPv6 for global IPv6
      addresses and CiscoTAddressIPv6s for scoped IPv6 addresses.";
    reference
     "RFC 2960 - Stream Control Transmission Protocol. R. Stewart,
      Q. Xie, K. Morneault, C. Sharp, H. Schwarzbauer, T. Taylor,
      I. Rytina, M. Kalla, L. Zhang, V. Paxson. October 2000.";
    smiv2:oid "1.3.6.1.4.1.9.19.99999.11";
  }

  smiv2:alias "ciscoCIB" {
    description
     "ciscoCIB is the root of the Cisco-assigned OID subtree for
      assignment to MIB modules describing managed objects that
      part of the CPE automatic configuration framework.";
    smiv2:oid "1.3.6.1.4.1.9.20";
  }

  smiv2:alias "ciscoCibMmiGroup" {
    description
     "ciscoCibMmiGroup is the root of the Cisco-assigned OID
      subtree for assignment to MIB modules describing managed
      objects supporting the Modem Management Interface (MMI),
      the interface that facilitates CPE automatic configuration.";
    smiv2:oid "1.3.6.1.4.1.9.20.1";
  }

  smiv2:alias "ciscoCibProvGroup" {
    description
     "ciscoCibStoreGroup is the root of the Cisco-assigned OID
      subtree for assignment to MIB modules describing managed
      objects contributing to the Configuration Information Base
      (CIB).";
    smiv2:oid "1.3.6.1.4.1.9.20.2";
  }

  smiv2:alias "ciscoPKI" {
    description
     "ciscoPKI is the root of cisco-assigned OID subtree for PKI
      Certificate Policies and Certificate Extensions.";
    smiv2:oid "1.3.6.1.4.1.9.21";
  }

}
